SignDynamicFormatModule	{iso standard 19794 sign-sign-processed-dynamic(11) modules(0) version(0)}
   DEFINITIONS
	 --PER INSTRUCTIONS
	 --This specifies that PER Encoding Instructions are to be applied
	 AUTOMATIC TAGS ::= 
   BEGIN
 

SignDynamicBlock ::= SEQUENCE {
	header GeneralHeader,
	body Body 
} 

GeneralHeader ::= SEQUENCE {
	formatId               			 IA5String ("SPD") (SIZE (10)),
	standardVersion              IA5String (SIZE (10)),
	     -- " 10" (space-one-zero) for this version
	lengthofRecord                INTEGER(0..4294967295),
	numberofRepresentations       INTEGER(0..65535),
	certificationFlag             INTEGER(0..255)}

Body ::= SEQUENCE {
	representation RepresentationHeaderValues,
	-- RepresentationBodyValues}   changed by TJ 20201011
	representationBody RepesentationBodyValues} -- changed end

RepresentationHeaderValues ::= SEQUENCE {
	reprsentationLength          INTEGER(0..4294967295),
	captureDateTime              CaptureDateTimeValues,
	captureDeviceTechId          INTEGER(0..255),
	captureDeviceVendId          INTEGER(0..65535),
	captureDeviceTypeId          INTEGER(0..65535),
	qualityRecord                QualityBlockValues,
	certificationRecord          INTEGER(0),
	xchannelScaling              ScalingValue,
	ychannelScaling              ScalingValue,
	tchannelScaling              ScalingValue,
	fchannelScaling              ScalingValue,
	numberofDynamicEvents        INTEGER (1..4294967295),
	numberofAveragingSamples     INTEGER (1..255)
}

CaptureDateTimeValues ::= OCTET STRING (SIZE (9))


QualityBlockValues ::= SEQUENCE {
   numberofQualityblocks INTEGER (0..255), 
   qualityblock SEQUENCE OF SEQUENCE{
			qualityScore INTEGER (0..100),
			qualityalgorithmVendId INTEGER (1..65535),
			qualityalgorithmId     INTEGER (1..65535)
	}

}


ScalingValue ::= SEQUENCE {
	exponent               INTEGER (-16..15),
	fraction               INTEGER (0..2047)}

RepesentationBodyValues ::= SEQUENCE {
	dynamicEventData DynamicEventData,
	featureData FeatureData,
	extendedData OCTET STRING OPTIONAL}

DynamicEventData ::= SEQUENCE {
	xCoordinate           INTEGER (-32768..32767),
	yCoordinate           INTEGER (-32768..32767),
	fValue                INTEGER (0..65535),
	timeValue             INTEGER (0..65535),
	typeofEvent           INTEGER (0..255)}
	
FeatureData ::= SEQUENCE {
	totalTime       INTEGER (0..65535),
	meanValues      OverallMeanValues,
	sdValues        StandardDeviation,
	cCoefficient    INTEGER (1..65535) }

OverallMeanValues ::= SEQUENCE {
	meanX           INTEGER (-32768..32767),
	meanY           INTEGER (-32768..32767),
	meanF           INTEGER (0..65535) }

StandardDeviation ::= SEQUENCE {
	sdX             INTEGER (0..65535),
	sdY             INTEGER (0..65535),
	sdF             INTEGER (0..65535) }
END
